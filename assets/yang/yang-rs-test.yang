module yang-rs-test {
  yang-version 1.1;
  namespace "urn:yang-rs:test";
  prefix t;

  description
    "Module exercising the schema APIs of yang-rs.";

  feature extra;

  identity protocol;

  identity routing-protocol {
    base protocol;
  }

  identity ospf {
    base routing-protocol;
    description
      "OSPF.";
  }

  identity ospfv2 {
    base ospf;
  }

  identity ospfv3 {
    base ospf;
  }

  identity rip {
    if-feature extra;
    base routing-protocol;
    status deprecated;
  }

  typedef percent {
    type uint8 {
      range "0..100";
    }
  }

  container types {
    leaf counter {
      type int16 {
        range "-10..-1 | 1..10" {
          error-message "Out of range.";
        }
      }
    }
    leaf big {
      type uint64;
    }
    leaf timeout {
      type uint16;
      default "30";
    }
    leaf ratio {
      type decimal64 {
        fraction-digits 2;
        range "0.5..100";
      }
    }
    leaf name {
      type string {
        length "1..8";
        pattern '[a-z]+';
        pattern 'x.*' {
          modifier invert-match;
          error-message "Can't start with x.";
        }
      }
    }
    leaf data {
      type binary {
        length "4";
      }
    }
    leaf level {
      type enumeration {
        enum low {
          value 1;
          description
            "Low level.";
        }
        enum high {
          value 10;
          status deprecated;
        }
      }
    }
    leaf flags {
      type bits {
        bit up;
        bit down {
          position 3;
          description
            "Down.";
        }
      }
    }
    leaf protocol {
      type identityref {
        base routing-protocol;
      }
    }
    leaf mixed {
      type union {
        type percent;
        type enumeration {
          enum auto;
        }
      }
    }
    leaf-list codes {
      type uint8;
    }
    choice format {
      case plain {
        leaf text {
          type string;
        }
      }
    }
    leaf peer {
      type leafref {
        path "../name";
      }
    }
    leaf limit {
      type union {
        type leafref {
          path "../counter";
        }
        type enumeration {
          enum none;
        }
      }
    }
  }

  container constraints {
    leaf protocol {
      type identityref {
        base routing-protocol;
      }
    }
    leaf level {
      type enumeration {
        enum low;
        enum high;
      }
    }
    leaf limit {
      type uint8;
      must ". <= 50" {
        error-message
          "Too high.";
      }
      must ". < ../max";
    }
    leaf max {
      type uint8;
    }
    container ospf {
      when "derived-from-or-self(../protocol, 't:ospf')";
      leaf area {
        type uint32;
      }
    }
    choice mode {
      case fast {
        when "level = 'high'";
        leaf burst {
          type uint8;
        }
      }
    }
  }

  container advanced {
    when "/t:constraints/t:level = 'high'";
    leaf enabled {
      type boolean;
    }
  }

  choice top-mode {
    case top-fast {
      when "t:constraints/t:level = 'high'";
      leaf top-burst {
        type uint8;
      }
    }
  }
}
